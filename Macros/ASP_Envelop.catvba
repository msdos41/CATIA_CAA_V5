Attribute VB_Name = "ASP_Envelop"
Sub CATMain()

Main_UI.Show 0


End Sub

Attribute VB_Name = "Main_UI"
Attribute VB_Base = "0{BDEA4E9C-0740-4407-B9E1-2AD51E8E07E0}{3A64E9AF-D11B-4716-A4D5-6723976987C6}"
Attribute VB_GlobalNameSpace = False
Attribute VB_Creatable = False
Attribute VB_PredeclaredId = True
Attribute VB_Exposed = False
Attribute VB_TemplateDerived = False
Attribute VB_Customizable = False
Private face1

Private line1

Private point1



Private Sub CommandButton1_Click()

If IsNumeric(Main_UI.TextBox1.Value) = True And IsNumeric(Main_UI.TextBox2.Value) = True And IsNumeric(Main_UI.TextBox3.Value) = True Then

  

   Dim i As Integer

   Dim j As Integer

   Dim k As Integer

   Dim partDocument1 As Document
   Set partDocument1 = CATIA.ActiveDocument

   Dim part1 As Part
   Set part1 = partDocument1.Part

   Dim hybridBodies1 As HybridBodies
   Set hybridBodies1 = part1.HybridBodies
   
   Dim hybridShapeFactory1 As Factory
   Set hybridShapeFactory1 = part1.HybridShapeFactory
   

'--create new folders--'


   Set folder1 = hybridBodies1.Add()
   Set rename1 = part1.CreateReferenceFromObject(folder1)
   part1.HybridShapeFactory.ChangeFeatureName rename1, "RefElement_" & TextBox4.Text

   Set folder2 = hybridBodies1.Add()
   Set rename2 = part1.CreateReferenceFromObject(folder2)
   part1.HybridShapeFactory.ChangeFeatureName rename2, "Envelop_" & TextBox4.Text
   
   
   
'--create original axis according to the input axis and point--'

   Dim parameters_line1 As Parameters
   Set parameters_line1 = part1.Parameters

   Dim hybridShapeLineExplicit1 As Parameter
   Set hybridShapeLineExplicit1 = line1

   Dim reference_line1 As Reference
   Set reference_line1 = part1.CreateReferenceFromObject(hybridShapeLineExplicit1)

   Dim parameters_point1 As Parameters
   Set parameters_point1 = part1.Parameters

   Dim hybridShapePointExplicit1 As Parameter
   Set hybridShapePointExplicit1 = point1

   Dim reference_point1 As Reference
   Set reference_point1 = part1.CreateReferenceFromObject(hybridShapePointExplicit1)

   Dim hybridShapePlaneNormal1 As HybridShapePlaneNormal
   Set hybridShapePlaneNormal1 = hybridShapeFactory1.AddNewPlaneNormal(reference_line1, reference_point1)


   Dim hybridBody1 As HybridBody
   Set hybridBody1 = hybridBodies1.Item("RefElement_" & TextBox4.Text)

   hybridBody1.AppendHybridShape hybridShapePlaneNormal1

   part1.InWorkObject = hybridShapePlaneNormal1

   part1.Update

   Dim ydir As HybridShapeDirection
   Set ydir = hybridShapeFactory1.AddNewDirectionByCoord(0#, 1#, 0#)

   Dim reference_plane1 As Reference
   Set reference_plane1 = part1.CreateReferenceFromObject(hybridShapePlaneNormal1)

   Dim original_axis As HybridShapeLinePtDir
   Set original_axis = hybridShapeFactory1.AddNewLinePtDirOnSupport(reference_point1, ydir, reference_plane1, 0#, 20#, False)

   hybridBody1.AppendHybridShape original_axis

   part1.InWorkObject = original_axis


'--apply loop to create several rotating axises according to original axis --'
 
   For i = 1 To TextBox1.Value

   j = i



      

       Set hybridShapeRotatei = hybridShapeFactory1.AddNewEmptyRotate()
       
       
       'Set parameters_original_axis = part1.Parameters

       'Set hybridShapeLineExplicit1 = parameters1.Item("a2")
       
       'Set hybridShapeLineExplicit1 = original_axis

       Set reference_original_axis = part1.CreateReferenceFromObject(original_axis)


       hybridShapeRotatei.ElemToRotate = reference_original_axis

       hybridShapeRotatei.VolumeResult = False

       hybridShapeRotatei.RotationType = 0

       'Set parameters2 = part1.Parameters

       'Set hybridShapeLineExplicit2 = line1

       'Set reference2 = part1.CreateReferenceFromObject(hybridShapeLineExplicit2)

       hybridShapeRotatei.Axis = reference_line1

       hybridShapeRotatei.AngleValue = 360 / TextBox1.Value * i

       Set hybridBody2 = hybridBodies1.Item("RefElement_" & TextBox4.Text)

       hybridBody2.AppendHybridShape hybridShapeRotatei

       part1.InWorkObject = hybridShapeRotatei

'--apply loop to create the final envelopes according to the rotating axises--'

           For k = 1 To TextBox2.Value / TextBox3.Value

               Set hybridShapeRotatej = hybridShapeFactory1.AddNewEmptyRotate()

               Set parameters3 = part1.Parameters

               Set hybridShapeSurfaceExplicit3 = face1
               
               Set reference3 = part1.CreateReferenceFromObject(hybridShapeSurfaceExplicit3)

               hybridShapeRotatej.ElemToRotate = reference3

               hybridShapeRotatej.VolumeResult = False

               hybridShapeRotatej.RotationType = 0

               Set reference4 = part1.CreateReferenceFromObject(hybridShapeRotatei)

               hybridShapeRotatej.Axis = reference4

               hybridShapeRotatej.AngleValue = TextBox3.Value * k

               Set hybridBody2 = hybridBodies1.Item("Envelop_" & TextBox4.Text)

               hybridBody2.AppendHybridShape hybridShapeRotatej

               part1.InWorkObject = hybridShapeRotatej

               part1.Update

            Next

     Next


MsgBox "Done!"


TextBox1.Text = ""
TextBox2.Text = ""
TextBox3.Text = ""
TextBox4.Text = ""

Else: MsgBox "请输入数字"


End If


End Sub

Private Sub CommandButton2_Click()


Unload Main_UI


End Sub

Private Sub CommandButton3_Click()

'Main_UI.Hide

Set docu1 = CATIA.ActiveDocument

Set selection1 = docu1.Selection


Dim inputface1(0)

Dim status_inputface1 As String

inputface1(0) = "HybridShapeSurfaceExplicit"

status_inputface1 = selection1.SelectElement2(inputface1, "select input", False)

CommandButton3.BackColor = vbGreen

Label_CB3.Caption = selection1.Item(1).Value.Name

If status_inputface1 = "cancel" Then Exit Sub

Set face1 = selection1.Item(1).Value

selection1.Clear

'Main_UI.Show



End Sub

Private Sub CommandButton4_Click()

'Main_UI.Hide

Set docu2 = CATIA.ActiveDocument

Set selection2 = docu2.Selection

Dim inputline1(0)

Dim status_inputline1 As String

inputline1(0) = "HybridShapeLineExplicit"

status_inputline1 = selection2.SelectElement2(inputline1, "select input", False)

CommandButton4.BackColor = vbGreen

Label_CB4.Caption = selection2.Item(1).Value.Name

If status_inputline1 = "cancel" Then Exit Sub

Set line1 = selection2.Item(1).Value

selection2.Clear

'Main_UI.Show 0

End Sub

Private Sub CommandButton5_Click()

'Main_UI.Hide

Set docu3 = CATIA.ActiveDocument

Set selection3 = docu3.Selection

Dim inputpoint1(0)

Dim status_inputpoint1 As String

inputpoint1(0) = "HybridShapePointExplicit"

status_inputpoint1 = selection3.SelectElement2(inputpoint1, "select input", False)

CommandButton5.BackColor = vbGreen

Label_CB5.Caption = selection3.Item(1).Value.Name

If status_inputpoint1 = "cancel" Then Exit Sub

Set point1 = selection3.Item(1).Value

selection3.Clear

'Main_UI.Show

End Sub

Private Sub Label2_Click()

End Sub

Private Sub TextBox1_Change()

End Sub

Private Sub UserForm_Click()

End Sub
