' ************************************************************************
' *                                                                      *
' *  Copyright Daimler AG 2005                                           *
' *  73734 Esslingen                                                     *
' *  Germany                                                             *
' *                                                                      *
' *  The copyright to the computer program(s) herein is the property     *
' *  of Daimler AG, Germany.  The program(s) may be used and/or          *
' *  copied only with the written permission of Daimler AG or in         *
' *  accordance with the terms and conditions stipulated in the          *
' *  agreement/contract under which the program(s) have been supplied.   *
' *                                                                      *
' ************************************************************************
'
' Purpose:     Change Document links of Drawing-Views
'
' ActiveDoc:   CATDrawing
'
' Contact:     Norbert Helmecke (Norbert.Helmecke@daimler.com)

' Author:      Kai Knospe (industriehansa.knospe@daimlerchrysler.com)
' Modified:    Alexander Burger (common.burger@daimlerchrysler.com)
'
' Version:     3.2/11.02.2010
'
' Description: The active Drawing Document will be linked to an active
'              CATPart or CATProduct. With this Method Drawing-Links can
'              be repaired. Drawing-Layouts can also be used with
'              different Geometry. The User will be prompted in an
'
'                       INPUTBOX
'
'              if all Dimensions should be deleted.
'
' Manual:      supplied via E-Mail as "ChangeLinks.ppt"
'
' ************************************************************************
' * Changes:     Version 2.0, 13.01.2006
' *              Dokumentabfrage der geöffneten Dateien wurde geändert
' ************************************************************************
' * Changes:     Version 3.0, 16.08.2007
' *              - Detail Sheets führen zu keinem Fehler mehr
' *              - Gesperrte Views werden nur noch auf Wunsch neu verlinkt
' *              - Es können nun mehrere Zeichnungen und Parts/Produkte
' *                geöffnet sein. Das Makro muss in einer Zeichnung
' *                Zeichnung gestartet werden. Mit einer INPUT-Box wählt
' *                der Anwender nun das Fenster aus, auf welches er die
' *                Zeichnung verlinken will. Dort muss er dann zu
' *                verlinkende Produkt auswählen. Es kann dabei entweder
' *                der oberste Knoten oder auch ein Sub-Produkt ausgewählt
' *                werden. Der Zeichnungslink verweist immer auf den
' *                obersten Knoten.
' ************************************************************************
' * Changes:     Version 3.1, 16.12.2008, Norbert Helmecke
' *              CatParts koennen nun auch verlinkt werden
' ************************************************************************
' * Changes:     Version 3.2, 11.02.2010, Anubhav Kumar
' *             -Check for Active Document added
' *             -Statistik  call added
' *             - MessageBox Headers
' *             -Select Object Function modified to avoid a crash
' *             -Escape key was not functioning…leading to a crash,hence modified
' ************************************************************************
'**Start Encode**#@~^oicAAA==@&@&@&6aYbWx,2X2VbmrY,B#CMkl(s+kP/4G;V9P(+~NnWbxnNE@&n!4sr1PWmjVnmDrKxS,W|HXGW1@&@&GkhPKf.CSkxT9W1E:UOP,P,P~P~v,/C\dPGDCAbxo~9Km;:UDP6(LmY@&fbhPKZG:aWUn	Y@&Gr:,lfK^;:xD/c#~~,P~P,~P,P~v,lD.CHPWWM~mVs,DKWY wMGN!mO/@&frh,qxa;Y}4L^OKHw`q#~~,P~PE~/m\nd,lVsGS+[Pkn^+^DkKxODXan@&GkhPK?4nYP,~P,PP,~~P,P,P~P~v,/C\dPGDCAbxo~j4+nY,6(Ln1Y@&fksPK#kh~P,P~~,PP,~P,PP,~~PEPkl-+d~GDChbUo,.rnSPr8%mO@&GrsPGdk	3P,P,~P,P~P,P~~,PP,~B,/l7ndPGDmhrxL~dkU3,64N+^O@&fkh~KIGWDKMW[!mDPP,P,~P,P~P,B~dm\+k~&GPIKGOPGW1Eh+UO,r8L^Y@&frh,kq~~,P~P,~,P~,P,PP,P,~P,B~mKxO.KVP7CDbl4^n~0KD,VGW2d@&fr:,r9,P~~,PP~~,P~P,~,P~,P,PB,mKUYMWsP7l.rm4V~0KDP^GGwk@&GkhPr]Y;D	#l^En~,PP~~,P~P,~EP]Y!Dx,\m.km4s+,0G.,0E	^YbWxk@&9ksPbrx[GS/~P,~P,P~~,PP~~,PvPkC7+d,x!:4D,G0,hrx9WAd@&fks~khDW9;^YkP,P~P~~,P~P,~P,B~dm\+d~	Eh4.,WW,DKWY wMGN!mO/@&frh,knMGN!mYg;h4D,P~P~~,P~PE~/m\nd,xEh8D~W6~Dtn,hbxNKh,WWMPOtPUnSPVbU3@&fks~dsbVKzwn~,P~P,~P,P~~,PPv~M+OEMUkPO4+,0k^+,OXa+@&fb:~dgl:~P,PP,~~P,P,P~P~~,PvPm;6bVrCMXP-CMkC4^n,0GMPkYDbxT~Wa+.lDkGUk@&fbhPkf+^nO+Gks+U/rG	/~P,~P,Pv~kl\ndBPr0,[b:n	/bWxkPk4W!V[P(+~[V+DnN@&fks~d.b+S1C:n~,P~P,~P,P~~,PPv~kl-+k~Dtn,\b+h,1mh+@&fr:,/K.KNE1OSb/Y,~~P,P,P~P~~EPdl7n/,l~sb/Y~AbY4Pms^PUm:/PK0,OtP.WKYR2MWN!^Yk@&fbh~/zN9n.W[;1Y~P,~P,P~~,PP~v,l;6bsbl.HPkYDbxT@&fb:~/hDG[!mYg;:(+D,~~P,P,P~Pv~M+dE^OPK0~O4+P(UaEOO~GXPWKD,YtPa.W9E^Y,YG~!/+@&9ksP4G.ChA6b/O/~~,P~P,~P,P~~EPY.;~~k6~9DCSk	oP6bdYk@&9ksP8/wDlsn2Xk/Dd~P,P,P~P~~,B~YM;+BPrW,mWUdDD;mDrKx~6Dm:+,+Xr/D/@&fb:~8Uwl1n2Xk/Dd~P,P,P~P~~,PvPD.E~~r6PnC.DzKDK[!mO,+Xk/D/@&9ksP8b	/AnMPP,~P,PP,~~P,P,P~B@&9b:~4;;DdW^VUYlO;kP~P,~,P~,PEPVKm0dYmY;/,WW~mP\bnhBPYM;nPb0,kOBd~^W^3[@&(f.CS26rdD/~',omVd@&(?wmm36b/O/,'~omV/@&4;sDmhn2XkkYdPx~wls/@&@&&x2;Dr4%n1YPXanv!b,',JnMW9;mDJ~PEP6U^XPh.W9EmDd~lM+,lsVGANv@&&Uw!Y68N+mOPHwn`8b,'~rnmDYrPE~l	N~nmDOd,lD~l^VWSn[~,NKxvY~WKDL+D~YKP^4mxon~Gq\PbU,Vr	+,*,E@&@&/W	/OP1/m\mm1mhP{PJ;4CxT+dkU3dEBP^/|\l1.n.,'PEfc EPE$m/n,HmmDKPAUtmx^+s+UOk@&fbhP1/{tdLC9D=P^/m\kouNM~',mdmtlmHCsP'PrRrP',mk{HmmjnD@&@&jE(P/):HlbU`*@&dEMMeCeCeMeMMCeMeCMeCeMMCeeMMCeMeCMCeMCeCeeCeCMeCeMeCeMMCeeCMeCeeCMMeCeCeMeMMCe@&dEjYmYrdDk3@&7EeMeCMCeMCeCeeCeCMeCeMeCeMMCeeCMeCeeCMMeCeCeMeMMCeMeCMeCeMMCeeMMCeMeCMCeMCeCee@&dGr:,ld?DlOHm:+vT#,BPzd~?DDbxLP8nbP/b:jmMk2O@&drU~AD.WM~"+d!:P16D@&dm/jYmYHCs+`ZbP{Pmkm\l11m:@&d/C^V~ZzPqzRjzkY+hjD-k1nc2am!Y+UmMrwD`EZzK9Jg)zJj5UK2t \b;I}R$bj3r~~{@&7mmYj^MkwOJb4.lMz:X2fbD+1YK.XBPEHKN;sRmmO\(/JB~m@&iJtl^?OCDJSPmd?DlOHm:+b@&irUPA.MW.,MKKW,!@&7B ORO ORR OO RO OO RRO O ORORR ORO RO ORR OORR ORO R OR O OO O RO ORO ORR @&dEMeCeeCMMeCeCeMeMMCeMeCMeCeMMCeeMMCeMeCMCeMCeCeeCeCMeCeMeCeMMCeeCMeCeeCMMeCeCeMe@&7Ee~Z4nm0PrW,Ytn~sl^DK~Sld,/DlDD+9~k	PCP9DCAbxo@&7BCeeCMMeCeCeMeMMCeMeCMeCeMMCeeMMCeMeCMCeMCeCeeCeCMeCeMeCeMMCeeCMeCeeCMMeCeCeMeMM@&d(0,HWDPc8&/fG^vJ9DmAbxLr#*PK4+	~2XkOPUE8@&i?+D~W|HXGG^P{P;bPq) zmOk7nfKm;hxY@&7ksrVPHwn,',KXa+gC:`G{tX9G1#@&i(0,/sbsnKHwPxPE9MlAk	LfKm;hxYE~:tnx@&7i?nDPKfDmhbUoGW^Es+UO,'PKmHHfW1@&72^/@&7d\dTAG6,E?Dl.O,Ytn~sl^DK~bx~mP9DlSk	LJBP-4;DrObml^SP1/{tdLC9D,[~Jl~qDGxT~YHwn~K0P[G1Eh+	Or@&7i2XkY,?!8@&i2UN,qW@&@&dBCMeCeeCMMeCeCeMeMMCeMeCMeCeMMCeeMMCeMeCMCeMCeCeeCeCMeCeMeCeMMCeeCMeCeeCMMeCeCeM@&7vCP/t^3,lss,ZlOrmP9W1;s+UD/,kx,Y4nPKwnxN~AbxNKA/c@&dEM~MY,Y4+~[MlAk	LPmx[~Dt+~2MW[E1O,W.,wmDY,NK^Es+UYk@&7vCeeCMeCeeCMMeCeCeMeMMCeMeCMeCeMMCeeMMCeMeCMCeMCeCeeCeCMeCeMeCeMMCeeCMeCeeCMMeCe@&@&7k	r	NGhk~',Z)P&bR	r	NGhk ;W;	Y,Bx!:(nD,WWPKwnU,hk	[WS/B@&7]+GksPCfG^!:nxDd`brU9WhdS, bPE90r	kDkW	PKWPDtnPmNG^!:+	O/,lDMCzB@&dbn.W[;1YdP{~!,B~dYPGW,Y4+,dDl.Dk	oP7l^;+E@&7sKD~r&P',qP:WPb	rx9WS/@&d7jY~W|\XGW^~{PZ)P&b bU9WAkR&Y+s`b(#cnCDxO~Er4NnmDPW6~OtPKwnx~/zK(b,9W1Ehn	YPrU,Y4+,Abx[Kh,kqE@&i7/wks+:X2n,'P:zw1lsncW|HHfGmb@&id(0,dsbVnPHw+~x,J9DmAbxLGW1E:xDEP:tnx@&d77(fDmA2Xk/Dd~',KMEn@&77AVd+@&7diqW~ksksn:X2+,x,JKMW9EmDfK^Es+UYrP6.,/sbs+:Xw~xPrnmDOfG^!:nxDEP:tnU@&dd77(?2l1nA6rkYkP',KM;+@&d7di?nO,lfK^Es+xDdckhDKN;mOdBPT#,xPK{\zGWm KMW[E1O@&d7idmfW1EsnxD/ckhDG[!mYkSP8#P{~rq@&did7kK.KN;mDdP{PrKMWN;^D/~_,q@&d7idE2Vk+@&7didvB,P~(6P/wrVYXan~',Jhl.Y9G1Eh+	OJ,K4n	@&d77iBvP,~,P~(?alm2Xr/D/~',K.;PBDGPSWD0~AkDt,wCDOdBP[+knVmO~6WVsGSkUo,sbxnkPmxN,VbU+,%{B@&d77iBB,~P,P?O~lGW1Eh+UOk`rnMGN!mOdB!#~x,WmHH9Km hDKNE1Y@&7didvB,P~~mfW1;:xYkcrnMW9E^YdS8#~',rq@&d77iBB~~,kKDK[!mOkP{PkhDK[E1YdP3Pq@&iddiv2	NP&W@&didAx[P(W@&d72	[P&0@&7g+6O@&@&dveCMCeMCeCeeCeCMeCeMeCeMMCeeCMeCeeCMMeCeCeMeMMCeMeCMeCeMMCeeMMCeMeCMCeMCeCeeCeCM@&iBMP&0~O4+D~kkPxK~dwmmPCx[~9DCh,[W1Ehn	YPG2xSPabY~hDKoDm:@&7BCeMeCeMMCeeCMeCeeCMMeCeCeMeMMCeMeCMeCeMMCeeMMCeMeCMCeMCeCeeCeCMeCeMeCeMMCeeCMeC@&@&i(WP(?al^+3ab/O/,xPwlsdPr.~(f.lS3XkdD/,'Pwl^d+,K4+	@&77bI+D;D	.l^;nP{P|@&7d\dTAG6vEAPd;M+POG,tC\~mP/zKGDlSk	LPz19PmP/):nlMOz;bKh.GN!mDPGwnUeJSP78ZMkOr1lVS~1/mHkL_N.*@&id2XkD~?!4@&dAx[~&0@&@&7BCeeCMMeCeCeMeMMCeMeCMeCeMMCeeMMCeMeCMCeMCeCeeCeCMeCeMeCeMMCeeCMeCeeCMMeCeCeMeMM@&dve,/DlOn,lPsrkY~W6~Dtn,wMWN!mDd@&iBMeCeMMCeeCMeCeeCMMeCeCeMeMMCeMeCMeCeMMCeeMMCeMeCMCeMCeCeeCeCMeCeMeCeMMCeeCMeCee@&@&7sKD,k(Px~ZPPW,rnMW[;1Y/~R,F@&didzN[hDKNE1Y,xPmfGm!:nUD/`b(~,!#cHC:PLPEPE~LPCfK^Es+UOk`k(S,!bRgGs+U1VmYEM+@&7dkn.W9E^Odk/D~',/nMG[E1YdkdY~',k(PL~J=PE~LP/)[9n.W9;1Y~LP74S6PE-4^0xSbxnW+NE@&dg+6D@&@&dEeCeMeMMCeMeCMeCeMMCeeMMCeMeCMCeMCeCeeCeCMeCeMeCeMMCeeCMeCeeCMMeCeCeMeMMCeMeCMeC@&7vCPbdV,Ed+M~Str1t,wDKN!^Y,YGP!/n@&iBeCMeCeeCMMeCeCeMeMMCeMeCMeCeMMCeeMMCeMeCMCeMCeCeeCeCMeCeMeCeMMCeeCMeCeeCMMeCeCe@&d(W,kKDK[E1Yd~@*PF~P4+U@&i7kn.KN!mYgEs8+MPxPrOqE@&ddq4k^+P;(UYv/hDGN;^D1;:(nD*P@!~ZPr.~;qUYvdhDG9E1Y1!:(nD*P@*',kK.KNE1O/@&ddidKDKN!mO1;h(+.P{~q	w;O~W6cdhDGN!^DSrkYBPmk{tdo_N.PLPElU+V^Y,wDK[;mDJBPE!Eb@&d7UN@&d7(6P/K.KN;mDH!:8D,'PrJ,Ptx@&diHdL~W6,EHmmDK~C4KDD+[P8z,Ed+ME~,\8/MkYr^mVSP1d|HdTC9D@&idAakDPjE(@&73	NP&W@&iknMG[E1YgEh4n.,'~Z&UYv/K.KNE^OgEh4.*@&7AVk+@&id&WPbn.W9E^OkP@!,qP:t+	@&7diHko$Wa~rns+md+,W2n	Pl~2MW[E1O,4n6WM+PME	Uk	o~Y4+~hmmDKZJBPmkm\/TC9D~[~E=P\l1.W,l8GMY+[E@&d7dAabY~UE(@&di2	[P&0@&dAx[~&0@&ij+DPW|\zfKm,'~Z)P&b bUNKhd &Y+hcmfGm!hxOk`bnDKN!^YgEh4DS~8##,v/V+1OnN,bx[WA~}4%+1OB@&dGmtXfG^cb^Yb-mYn,BmmYb\mO+kPd+^+^ONPSrx9WhE@&7?Y,Wm?nsmOkKUP{P/):qb )1Yr\9Km;s+	YRU+^nmDkGx,B[n1VlMCYbWxKW~/VmOkGU,W8L^YE@&7(6PKz21C:c;bP&bcbmDk7nfKm;:xOb,'PrKDKNE1O9W1Es+UYE~:tnx@&7dt/L$K6PEjVnmD~hDG9E1YPKD,jE(OKDKN;^DP0K.P	+h,srx0JBP-46F}xsXB~mk{\dTCN.~LPE),9Km;s+	YP6WM~VbxVJ@&d7G|?+^nmDkW	 /VlM@&7djnDPGZKhwKxnUDP'~jVnmD6(Ln1YvqxaED64N+^Y:X2nBPmkmHkoC9.~[,J=?nVn^DP2DK[E1Y~GMP/;8 w.W9;1Y~6WMPY4+,U+SPsk	3Eb@&d2^d+@&ddUnOPKZK:2WUn	Y~',/b:q) zmYr-fGm!hxOcnmDY@&dAUN,qW@&iqW~KZWs2W	+xD~(/,1KY4kUL,K4+	~2XkO~UE4@&@&@&dvPCMCeMCeCeeCeCMeCeMeCeMMCeeCMeCeeCMMeCeCeMeMMCeMeCMeCeMMCeeMMCeMeCMCeMCeCeeCeCM@&iB~e,jdnMPq	O+MlmDrGx=@&iB~e~ik+.PSrV^P8n,l/Vn9~~k6~mVs,fb:+	/bGxkPdtKEs[,4+,[+^+Y[ P:tP;/n.,tC/,OW@&dv~CP+UOD~Xd,W.,xKR@&iB,MPhDnN0rUNPbdP	W@&iv~eCeCeMeMMCeMeCMeCeMMCeeMMCeMeCMCeMCeCeeCeCMeCeMeCeMMCeeCMeCeeCMMeCeCeMeMMCeMeC@&@&i4r^+Pd9VnY9b:n	/bWxkP@!@*Pr53?rP)U9P/GnVY+Grh+	/bWU/~@!@*PE1}E@&idd9V+OnGkh+	dbWUkP{Pj;lkn`,{@&diqU2!YAKa`rf+^nO+,PGkh+UdbWU/,rx,f.CSkxL~vXn/JUK#_=JBPmk{tdo_N.PLPElG+VO+cRRrS~Jgrr#b@&77&0~`k9+^+OnGk:nUkkGxk~{PEr#,Ktx@&7diZ)K&b )1Yk7nfKmEsnUYc?VnmOrKx Z^nlM@&77i26rO,?;4@&7i2U9P&0@&iUN@&@&7B,eMMCeeCMeCeeCMMeCeCeMeMMCeMeCMeCeMMCeeMMCeMeCMCeMCeCeeCeCMeCeMeCeMMCeeCMeCeeCM@&dEPCPU+A~^kU3,Gx,lss,\knAkPGD,G	P;	VKm3N,-khdPKxsz@&dB,MeCeeCMMeCeCeMeMMCeMeCMeCeMMCeeMMCeMeCMCeMCeCeeCeCMeCeMeCeMMCeeCMeCeeCMMeCeCeM@&@&7(bU/SnD,'~\koAGavJ]+ sbxV,VKm3N,-khdgr~~-(5+kHW;lx1ns~1/|Hdou[M[~J=~qTxG.PVG^0+[P7rhdQJ*@&@&iB,MeCeMeCeMMCeeCMeCeeCMMeCeCeMeMMCeMeCMeCeMMCeeMMCeMeCMCeMCeCeeCeCMeCeMeCeMMCeeC@&dEPe,LGPDtMW;o4~mVsPU4+Yd~mxPCs^P#kAk@&7EPCeeCeCMeCeMeCeMMCeeCMeCeeCMMeCeCeMeMMCeMeCMeCeMMCeeMMCeMeCMCeMCeCeeCeCMeCeMeCe@&@&isWM~kxP',q~KKPKf.lAr	o9W1;:xO Ut+nOkR/W!UD@&7i?YPK?4n+DPxPKf.CSkxT9W1E:UORUt+O/ (D+h`bB#@&d7(6P1GO,`G?4nY &/G+Ymk^bP:tnx@&d77wWD,rq,'P2~PW,WUtn+O jknhk ZKEUO@&dd77U+OPK#b+A,',W?4+ORjknhkR(O:`b(#@&ddi7d.b+S1C:n~{PG.bnhc1Ch@&@&77idvPCMCeMCeCeeCeCMeCeMeCeMMCeeCMeCeeCMMeCeCeMeMMCeMeCMeCeMMCeeMMCeMeCMCeMCeCeeCeCM@&id7dEPM~G+VO+,fksnU/bW	/SPrW,/nV^YN@&7iddv~CeMeCMCeMCeCeeCeCMeCeMeCeMMCeeCMeCeeCMMeCeCeMeMMCeMeCMeCeMMCeeMMCeMeCMCeMCeCee@&di7d&0~1KY~Gjk+S SKm3UOCY!/,r.PcGjknhcJW13jOmYEd~zx[P()	/AD,'P74In/*PPtx@&7iddi8Z!DSK^V?DlDEdPx~K.r+S SKmVjDlY;d@&d7di7K.rhcSW13UOlDEdP{PoC^/+@&7didd&W~Wjkh frhxdkKU/cZG;	YP@*~ZP)x9~kfn^+D+fb:U/bWU/,'~EI2?r~K4+x@&77didi4ksn,W#kARGkhn	/kGUkR/W!UDP@*,!@&ddidi7dK.r+SR9rs+xkrW	/R"nhW7+,`G.rnSR9ksnxkkGUkRZG;	Yb@&i7id7ixN@&di7di2UN,qW@&@&ddi7dEPeCMMeCeCeMeMMCeMeCMeCeMMCeeMMCeMeCMCeMCeCeeCeCMeCeMeCeMMCeeCMeCeeCMMeCeCeMeMMC@&7di7dEPM~&0PO4P#kA,1Cs+,k/DP	GY,B\lbx~#b+hE~h4km4~r/,Y4+~/4nY~kDd+^0~GMPY4n@&d7di7EPM,B~lm0oMGE	N~.b+Av,htb^t,k/,;d+9P6W.PO4PE}rm4x;UT/DC4s+UJB~9+sYPl^V@&7did7B,e~#b+h Jk	3/,CUN,l9N~l~sbxVPDGPDtn~Uwl^nv&9#,9Km;s+	Y@&idi7dEPMeCeMMCeeCMeCeeCMMeCeCeMeMMCeMeCMeCeMMCeeMMCeMeCMCeMCeCeeCeCMeCeMeCeMMCeeCMeCe@&@&77did&0~/#rhHlsnP@!@*~EtlkU~jknhr~}D~k.b+hglsnP@!@*~J~l^VTDW!UN,.kAEP:tx@&d77id7?OPKSrU0P'~Gjknhc!xnMlDk\SbU3k@&7did77bI+D;D	.l^;nP{PKSrxV "+hW7nb^VJr	3/cb@&d7di7iWJbx0Rb9Ndrx0PGZK:2G	+xD@&diddi3UN,q6@&7d77iW9DmAk	o9G1E:nUDR)mDr7lO@&iddidK#kh Mxn.mYk7nAtl7rGDcjaNCYn@&id7diG.b+A dWmVjDlOEk~{P8;EMSW13UOlDEd@&id77AxN,(0@&ddiHn6D@&id3x[~&0@&dgn6D@&3U9P?;8@&@&vPCMCeMCeCeeCeCMeCeMeCeMMCeeCMeCeeCMMeCeCeMeMMCeMeCMeCeMMCeeMMCeMeCMCeMCeC@&B,e,oE	mOkKxl~U+V^Y}4L^O@&EPCeMeMMCeMeCMeCeMMCeeMMCeMeCMCeMCeCeeCeCMeCeMeCeMMCeeCMeCeeCMMeCeCeMeMMCe@&s!UmDkGU,?+sn1Y64Nn1YcKq	wEDr(%+1YSPk?OCDE/:n6D#@&i9r:,?DlOEd@&iWm?s+1YrG	RZsnmD@&dUOmY;kP{PW|?s+1YrW	Rjn^+mD3V:+	O+`Kq	w;Y68N+^YB~/UYCO!/KnaD~~smsk+b@&d&0PUYmOEkPxPrZCU1+Vr~K4+x@&77?Y,?nVn^Dr8L^Y,'~HKYtrUT@&7dAabY~wE	mYbW	@&dAVd+@&d7jYPUnVmY}8%+1Y,'~WmjVnmDrW	R(O:`qbc.CV!n@&d3	N,q0@&2	[PwEUmDkGU@&BeCMeCeeCMMeCeCeMeMMCeMeCMeCeMMCeeMMCeMeCMCeMCeCeeCeCMeCeMeCeMMCeeCMeCeeCMMeCeCe@&B(d,l^Yb-+,NG^!:+UO,WWPDza+~kYHw@&EeCMeCeMeCeMMCeeCMeCeeCMMeCeCeMeMMCeMeCMeCeMMCeeMMCeMeCMCeMCeCeeCeCMeCeMeCeMMCee@&oE	mYbGUP(qkfGmcd:X2#@&7fb:~dGWmHCs+SPb3MDGM@&@&dr	PA.DKD~I/;hP1aY@&d/GG^1m:PxP/):q)Rz^Yb\n9KmEhn	Y 1mh)~b2MDWMP{~2MD 1!:8nM@&d}UPADDK.~MKKKPT@&78&/9W1~',K.;@&d(W,`cq	jDDckfKm1m:SPkKzw*Px~Z#P}.Pvk2M.GD,@!@*PT#b~:tnx@&7d(qd9KmPx~wls/@&id\ko~W6,Jz^Yb\nPGW^;s+xD~:!/Y,8nPmPrP'PdPHwSP78ZMkOr1lVS~1/mHkL_N.@&dAxN,q6@&2	N~s!x^ObWx@&@&@&@&UtUKAA==^#~@
